Language="VBSCRIPT"

Sub CATMain()

Set partDocument1 = CATIA.ActiveDocument

Set selection1 = partDocument1.Selection

Set visPropertySet1 = selection1.VisProperties

Set part1 = partDocument1.Part

Set hybridBodies1 = part1.HybridBodies

Set hybridBody1 = hybridBodies1.Item("Profile")

Set sketches1 = hybridBody1.HybridSketches

Set sketch1 = sketches1.Item("Passfederbohrung")

Set sketches1 = sketch1.Parent

Dim bSTR1
bSTR1 = sketch1.Name

selection1.Add sketch1

Set visPropertySet1 = visPropertySet1.Parent

Dim bSTR2
bSTR2 = visPropertySet1.Name

Dim bSTR3
bSTR3 = visPropertySet1.Name

visPropertySet1.SetShow 0

selection1.Clear 

Set selection2 = partDocument1.Selection

Set visPropertySet2 = selection2.VisProperties

Set sketches1 = sketch1.Parent

Dim bSTR4
bSTR4 = sketch1.Name

selection2.Add sketch1

Set visPropertySet2 = visPropertySet2.Parent

Dim bSTR5
bSTR5 = visPropertySet2.Name

Dim bSTR6
bSTR6 = visPropertySet2.Name

visPropertySet2.SetShow 1

selection2.Clear 

End Sub
